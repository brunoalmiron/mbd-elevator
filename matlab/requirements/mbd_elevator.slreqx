# mbd_elevator

## REQ01: Conforto do Usuário Segundo ABNT (Container)
O sistema deve apresentar operação confortável, com aceleração e desaceleração suaves, sem trancos ou solvancos.

### REQ02: Aceleração máxima permitida do sistema (Functional)
O elevador não deve ultrapassar a aceleração máxima.
